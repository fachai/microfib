module microfib {
    yang-version 1;
    namespace "urn:opendaylight:params:xml:ns:yang:microfib";
    prefix "microfib";

    revision "2015-01-05" {
        description "Initial revision of microfib model";
    }
}
